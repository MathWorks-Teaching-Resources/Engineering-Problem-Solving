# BungeeRequirementsBase

## #1: The bungee jumping system shall be operable all year round for the majority of adults. (Functional)

### #2: The bungee jumping system shall function at a maximum temperature of 50°C. (Functional)

### #3: The bungee jumping system shall support a maximum weight of 120 kg. (Functional)

### #4: The bungee jumping system shall support a jumper's maximum surface area of 2 m². (Functional)

### #5: The bungee jumping system shall have a starting height of 80 m. (Functional)

### #6: The bungee jumping system shall have an unstretched cord length of 20 m. (Functional)
