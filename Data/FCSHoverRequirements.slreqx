# FCSHoverRequirements

## #1: The drone shall be capable of transporting and delivering a 1 kg package. (Functional)

### #2: The Flight Control System shall provide stability information to the airframe for continued maneuverability through the mission. (Functional)

### #13: The Flight Control System shall define the flight phase for the drone which includes takeoff, landing, cruise, and hover. (Functional)

#### #3: Flight Phase - Takeoff (Functional)

#### #4: Flight Phase - Cruise (Functional)

#### #5: Flight Phase - Landing (Functional)

#### #6: Flight Phase - Hover (Functional)

##### #7: During the hover phase, the The Flight Control System software shall prevent the quadcopter from contacting the ground by maintaining an altitude of at least 5 m above ground level. (Functional)

##### #8: The Flight Control System software shall define hover flight phase by providing an input velocity of 0 m/s. (Functional)

##### #9: The Flight Control System software shall maintain a constant ~0 m/s measured velocity during hover phase. (Functional)

##### #10: The Flight Control System software shall incorporate the mass of the drone as 7 kg. (Functional)

##### #11: The Flight Control System software shall incorporate the acceleration of gravity as -9.81 m/s^2. (Functional)

## #14: The drone shall achieve a minimum flight range of 30 m per charge. (Functional)
